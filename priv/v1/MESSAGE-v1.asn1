--- Протокол Месенжера Сохацького v1 для UDP мультікаст в локальних мережах

MESSAGE-v1 DEFINITIONS ::= BEGIN

    IMPORTS ContentInfo FROM CryptographicMessageSyntax-2009
            Certificate FROM PKIX1Explicit-2009 ;

    OS  ::= ENUMERATED { apple (1), microsoft (2), google (3), ericsson (4), nokia (5), cisco (6) }
    P2P ::= SEQUENCE { from OCTET STRING, to OCTET STRING }
    MUC ::= SEQUENCE { room OCTET STRING }

    CHATString ::= OCTET STRING

    -- 01 Authority (CA)

    Feature ::= SEQUENCE { id OCTET STRING, key OCTET STRING, value OCTET STRING, group OCTET STRING }
    AuthorityMethod ::= ENUMERATED { announce (0), register (1), authenticate (2), dismiss (3), renew (4) }
    Authority ::= SEQUENCE {
       session OCTET STRING,
       type AuthorityMethod,
       cert OCTET STRING,
       settings SEQUENCE OF feature Feature }

    -- 02 File (FS)

    File ::= SEQUENCE {
       id OCTET STRING,
       mime OCTET STRING,
       payload ANY,
       parentid OCTET STRING }

    -- 03 Message (MNESIA)

    Channel ::= SEQUENCE { channel OCTET STRING }
    MessageType ::= ENUMERATED { sys (1), reply (2), forward (3), read (4), edited (5) }
    MessageStatus ::= ENUMERATED { async (1), delete (2), clear (3), update (4), edit (5) }
    MessageFeed ::= CHOICE { p2p [0] P2P, muc [1] MUC, chan [2] Channel }
    Message ::= SEQUENCE {
       id CHATString,
       feed MessageFeed,
       from CHATString,
       to CHATString,
       files SEQUENCE OF file File,
       type MessageType,
       link CHOICE { empty [1] NULL, message [2] Message },
       seenby CHATString,
       repliedby CHATString,
       mentioned SEQUENCE OF name CHATString,
       status MessageStatus DEFAULT clear }

    -- 04 Ack (TCP REPLY PUSH)

    Ack ::= SEQUENCE { table OCTET STRING, id OCTET STRING }

END
